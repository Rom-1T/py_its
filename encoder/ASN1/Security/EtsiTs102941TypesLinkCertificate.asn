EtsiTs102941BaseTypes
{ itu-t(0) identified-organization(4) etsi(0) itsDomain(5) wg5(5) ts(102941) baseTypes(3) version3(3) }

DEFINITIONS AUTOMATIC TAGS ::=
BEGIN

Question ::= SEQUENCE {
    id        INTEGER,
    question  IA5String
}

Answer ::= SEQUENCE {
    id        INTEGER,
    answer    BOOLEAN
}

END
